; auto load the dll file by C# - 2023-08-06
(command-s "_.netload" "D:\\dataflow.code\\dataflow-cs\\TargetDLL\\dataflow-cs.dll")
; (command-s "_.netload" "D:\\dataflowcad\\dataflowcad\\dataflowNet\\TZSolution.dll")
