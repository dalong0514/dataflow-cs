; auto load the  C#  dll file
(command-s "_.netload" "D:\\fsd-cad\\src\\dataflowNet\\TZSolution.dll")
; (command-s "_.netload" "D:\\fsd-cad\\src\\DLNet\\dataflow-cs.dll")
(command-s "_.netload" "D:\\dataflow.code\\dataflow-cs\\dataflow-cs\\obj\\Debug\\dataflow-cs.dll")

(command-s "DLGsAddMenu" "")
